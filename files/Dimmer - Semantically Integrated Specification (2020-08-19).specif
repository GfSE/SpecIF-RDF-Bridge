# Dimmer - Semantically Integrated Specification (2020-08-19)
This specification method integrates and represents:
- processes, system composition and requirements (dynamic, static and detail views)
- mechanic, electric and software components with their interfaces.

It is important to understand, that all plans (diagrams) are views of a common system engineering model, sometimes called 'system repository'. Thus, consistency is always maintained.

The model elements are connected with relations, most of which are defined by positioning graph elements. For example, if a system component is drawn within another, a relationship 'contains' is created in the logic representation of the engineering model. Other relations, such as a system component 'complies-with' a requirement are created manually.  

Also, the documents are generated from the system engineering model. The ordering is in most projects (it can be rearranged, however, if appropriate):
- All plans
- A glossary with descriptions of all model elements appearing on one or more plans
- A hierarchically ordered list of requirements
- A list of open issues.
Please note that plans list related model elements and model elements list related requirements .. and vice versa. Active hyper-links are used, so that it is easy to jump between related model elements.

Further information is given in Appendix 'Method'.
- Rights: Creative Commons 4.0 CC BY-SA, https://creativecommons.org/licenses/by-sa/4.0/

## Project Information (SpecIF:Heading)
- dcterms:description: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
  This is a small show-case illustrating the basic concepts for integrated mechatronic system specification. In addition to the original text and diagrams you will find logical relations between the information elements. Most relations are derived automatically from the diagrams; the resulting semantic net lends itself for navigation, search and audit.
  The specification integrates and represents:
  - processes, system composition and requirements (dynamic, static and detail views)
  - mechanic, electric and software components with their interfaces.
  It is important to understand, that all plans (diagrams) are views of a common system engineering model, sometimes called 'system repository'. Thus, consistency is always maintained.
  The model elements are connected with relations, most of which are defined by positioning graph elements. For example, if a system component is drawn within another, a relationship 'contains' is created in the logic representation of the engineering model. Other relations, such as a system component 'complies-with' a requirement are created manually.
  Also, the documents are generated from the system engineering model. The ordering is in most projects (it can be rearranged, however, if appropriate):
  - All plans
  - A glossary with descriptions of all model elements appearing on one or more plans
  - A hierarchically ordered list of requirements
  - A list of open issues.
  Please note that plans list related model elements and model elements list related requirements .. and vice versa. Active hyper-links are used, so that it is easy to jump between related model elements.
  Stakeholders:
  | Name | Organisation | Telephone | Email |
  | --- | --- | --- | --- |
  | Vorname Nachname | Hersteller AG |  |  |
  Legend:
  To distinguish their type, element names are preceded by one of the following symbols:
  | ▣ | Plan | A 'Diagram' is a graphical model view with a specific communication purpose, e.g. a business process or system composition. |
  | --- | --- | --- |
  | ■ | Actor (Role, Function) | An 'Actor' is a fundamental model element type representing an active entity, be it an activity, a process step, a function, a system component or a role. |
  | ● | State (Information) | A 'State' is a fundamental model element type representing a passive entity, be it a value, a condition, an information storage or even a physical shape. |
  | ♦ | Event | An 'Event' is a fundamental model element type representing a time reference, a change in condition/value or more generally a synchronisation primitive. |
  | ✶ | Feature | A 'Feature' is an intentional distinguishing characteristic of a system, often a unique selling proposition. |
  | ↯ | Requirement | A 'Requirement' is a singular documented physical and functional need that a particular design, product or process must be able to perform. |

## System Composition (SpecIF:Heading)
- dcterms:description: .. showing the system and its composition of modules (at a higher level) and components (at a lower level). The relevant interfaces between the disciplines mechanical, electrical and software engineering are shown.

## Color coding (SpecIF:Diagram)
- SpecIF:Diagram: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
- SpecIF:Notation: FMC Block Diagram
- Status: 40_approved
- HIS:SupplierStatus: not-applicable
- HIS:OemStatus: not-to-evaluate

## SmartHome System (SpecIF:Diagram)
- dcterms:description: The Smart-Home-System consists of sensors on the left side, the controller in the middle and the actuators on the right side.
- SpecIF:Diagram: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
- SpecIF:Notation: FMC Block Diagram
- Status: 10_initial
- HIS:SupplierStatus: to-clarify
- HIS:OemStatus: to-evaluate

## Flush-mounted Dimmer (SpecIF:Diagram)
- dcterms:description: .. showing the components of the device with their interfaces.
- SpecIF:Diagram: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
- SpecIF:Notation: FMC Block Diagram
- Status: 10_initial
- HIS:SupplierStatus: not-agreed
- HIS:OemStatus: not-accepted

## Dimmer Module (SpecIF:Diagram)
- SpecIF:Diagram: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
- SpecIF:Notation: FMC Block Diagram
- Status: 10_initial
- HIS:SupplierStatus: partly-agreed
- HIS:OemStatus: to-evaluate

## Scenarios (SpecIF:Heading)
- dcterms:description: .. showing the behavioral aspects of system design, both from external user perspective ('black box') and from internal perspective ('white box').

## Dimming (SpecIF:Heading)

## User Activity (SpecIF:Diagram)
- dcterms:description: This shows the defined sequences of manual operation to activate the device.
- SpecIF:Diagram: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
- SpecIF:Notation: BPMN Process Model
- Status: 20_drafted
- HIS:SupplierStatus: agreed
- HIS:OemStatus: accepted

## Double-Button Observer Software (SpecIF:Diagram)
- dcterms:description: This software module discriminates the user's activity (operation sequence) and submits corresponding events/commands to the actuator. This software is generic with respect to the actuator, it can be used for [[dimmer]]s, [[shading]] devices and others.
- SpecIF:Diagram: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
- SpecIF:Notation: BPMN Process Model
- Status: 20_drafted
- HIS:SupplierStatus: agreed
- HIS:OemStatus: accepted

## Dimmer Controller Software (SpecIF:Diagram)
- dcterms:description: This software decodes the commands and controls the timely behavior of the actuator.
- SpecIF:Diagram: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
- SpecIF:Notation: Petri Net
- Status: 20_drafted
- HIS:SupplierStatus: agreed
- HIS:OemStatus: accepted

## Requirements (SpecIF:Heading)

## Function (SpecIF:Heading)
- dcterms:description: The requirements related to the product function.

## Dim an electric load (IREB:Requirement)
- dcterms:identifier: REQ_014
- dcterms:description: The user can set the intensity level of an electric load such as a light [[bulb]]. Pressing a button 'up' or 'down', the intensity is increased or decreased following a quasi-stepless ramp.
- Status: 40_approved
- SpecIF:Priority: 2_medium
- Perspective: User
- Discipline: Mechanics, Electronics, Software
- HIS:SupplierStatus: agreed
- HIS:SupplierComment: Our solution does this perfectly.

## Switch an electric load (IREB:Requirement)
- dcterms:identifier: REQ_016
- dcterms:description: The user can immediately switch 'on' or 'off' the electric load. The intensity set to the maximum resp. minimum level, as defined by installation parameters.
- Status: 40_approved
- SpecIF:Priority: 2_medium
- Perspective: User
- Discipline: Electronics, Software

## Set dimming parameters (IREB:Requirement)
- dcterms:identifier: REQ_015
- dcterms:description: During system setup, the installer can modify the following parameters:
  - maximum intensity
  - minimum intensity
  - dimming speed (intensity ramp when dimming)
- Status: 30_submitted
- SpecIF:Priority: 2_medium
- Perspective: User
- Discipline: Software

## Minimum button size (IREB:Requirement)
- dcterms:identifier: REQ_009
- dcterms:description: The button size must not be less than 2 cm in diameter.
- Status: 40_approved
- SpecIF:Priority: 1_high
- Perspective: User
- Discipline: Mechanics
- HIS:SupplierStatus: to-clarify
- HIS:SupplierComment: We did not find the actual minimum dimensions of the buttons.

## Electric load is 120 W (IREB:Requirement)
- dcterms:identifier: REQ_001
- dcterms:description: The power stage must allow an electric load of 120 W.
- Status: 30_submitted
- SpecIF:Priority: 1_high
- Perspective: User
- Discipline: Electronics
- HIS:SupplierStatus: to-clarify
- HIS:SupplierComment: For which time period?  Permanent load?

## Quality (SpecIF:Heading)
- dcterms:description: The requirements related to quality characteristics of the product.

## Instant use (IREB:Requirement)
- dcterms:identifier: REQ_003
- dcterms:description: 85% of an arbitrarily selected group of test users understands and can use the system without reading a manual.
- Status: 40_approved
- SpecIF:Priority: 2_medium
- Perspective: User
- Discipline: Mechanics, Software
- HIS:SupplierStatus: agreed

## Instantaneous reaction (IREB:Requirement)
- dcterms:identifier: REQ_008
- dcterms:description: The reaction time of the system to user input is 'instantaneous' (< 0,5 sec).
- Status: 60_completed
- SpecIF:Priority: 1_high
- Perspective: User
- Discipline: Software
- HIS:SupplierStatus: agreed
- HIS:SupplierComment: Mais bien sûr.
- HIS:OemStatus: to-evaluate
- HIS:OemComment: Das ist ganz wichtig für uns.

## Consistent system behavior (IREB:Requirement)
- dcterms:identifier: REQ_011
- dcterms:description: The system's behavior must be consistent. For example, controlling a dimmer must correspond with controlling a shade.
- Status: 40_approved
- SpecIF:Priority: 2_medium
- Perspective: User
- Discipline: Mechanics, Software

## No dead-locks (IREB:Requirement)
- dcterms:identifier: REQ_010
- dcterms:description: Under no circumstances the system may get stuck in a dead-lock. I.e. every sequence of input stimulation must be supported, even arbitrary sequences. Input stimulation which is not supported in a given system state is either refused with an error message, if a feedback channel is available, or it is simply ignored, otherwise.
- Status: 40_approved
- SpecIF:Priority: 1_high
- Perspective: System
- Discipline: Electronics, Software

## Overload protection (IREB:Requirement)
- dcterms:identifier: REQ_002
- dcterms:description: The dimmer unit is protected against resistive overload and against any capacitive or inductive loads.
- Status: 30_submitted
- SpecIF:Priority: 2_medium
- Perspective: User
- Discipline: Electronics

## Auto shut-off (IREB:Requirement)
- dcterms:identifier: REQ_007
- dcterms:description: In case of over-temperature the device is shut-off automatically by an electronic circuit.
- Status: 30_submitted
- SpecIF:Priority: 2_medium
- Perspective: System
- Discipline: Electronics

## Constraints (SpecIF:Heading)
- dcterms:description: The requirements related to constraints for product conception, such as regulations or technical choices made upfront.

## Compliance with industry standards (IREB:Requirement)
- dcterms:identifier: REQ_012
- dcterms:description: The system must comply with industry standards. Besides legal and safety requirements, compatibility with existing electrical installations, tools and commercial components is desired.
- Status: 40_approved
- SpecIF:Priority: 2_medium
- Perspective: User
- Discipline: Mechanics, Electronics, Safety

## Industry-standard mounting (IREB:Requirement)
- dcterms:identifier: REQ_004
- dcterms:description: The product fits into an industry-standard [[housing]] for flush-mounted devices (diameter ⌀68 mm). It is fixed with two screw-activated claws.
- Status: 30_submitted
- SpecIF:Priority: 1_high
- Perspective: System
- Discipline: Mechanics

## Fire protection (IREB:Requirement)
- dcterms:identifier: REQ_005
- dcterms:description: The product must withstand 650°C (VDE 0606-1).
- Status: 30_submitted
- SpecIF:Priority: 1_high
- Perspective: User
- Discipline: Mechanics, Electronics

## Galvanic Isolation (IREB:Requirement)
- dcterms:identifier: REQ_013
- dcterms:description: The load circuit with power stage is galvanically isolated from the controller.
- Status: 30_submitted
- SpecIF:Priority: 1_high
- Perspective: System
- Discipline: Electronics
- HIS:SupplierComment: This is standard for all our products: expensive, but effective.
- HIS:OemStatus: to-evaluate

## Complete state-machine (IREB:Requirement)
- dcterms:identifier: REQ_006
- dcterms:description: The system is controlled by a complete state-machine and must not have any dead-lock state.
- Status: 40_approved
- SpecIF:Priority: 2_medium
- Perspective: System
- Discipline: Software

## Model-Elements (Glossary) (SpecIF:Heading)

## Type 'Actor' (SpecIF:Heading)
- dcterms:description: An 'Actor' is a fundamental model element type representing an active entity, be it an activity, a process step, a function, a system component or a role.

## Assembly Frame (FMC:Actor)
- dcterms:description: Mounting frame screwed to or into a wall.

## Briefly press Down-button (FMC:Actor)
- dcterms:description: Press down-button <x ms.

## Briefly press Up-button (FMC:Actor)
- dcterms:description: Press up-button <x ms.

## Bulb (FMC:Actor)
- dcterms:description: Dimmable candescent light-bulb 230V.

## Dimmer Controller Software (FMC:Actor)
- dcterms:description: Input commands (events):
  - up-long → increase brightness
  - down-long → decrease brightness
  - release → stop dimming, keep brightness
  - up-short → switch to maximum
  - down-short → switch to minimum
  - inappropriate commands are ignored (e.g. up-long when maximum is set).
  - set parameters
  Four parameters influence the behavior of the particular device:
  - minimum value (default: 0%)
  - maximum value (default: 100%)
  - ramp-up speed (default: 10% per sec)
  - ramp-down speed (default: 10% per sec)

## Dimmer Electronics (FMC:Actor)
- dcterms:description: The Dimmer Electronics is a printed circuit board with low-power micro-processor, memory, binary as well as analog I/O signals and a power stage supporting the specified electric load.
  Diagramm:
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
## Dimmer Module (FMC:Actor)
- dcterms:description: The actuator module with dimmer function for resistive loads.

## Double Button (FMC:Actor)
- dcterms:description: The Double Button (a sensor unit) is a versatile all-mechanical unit used for multiple purposes. The mechanical position is transferred with a rod per button to the next unit where it is converted to an electrical signal.

## Double-Button Observer Software (FMC:Actor)
- dcterms:description: This is an observer of the double-button sensor. It distinguishes short and long pressing in the 'up' and 'down' directions. A discriminator may send five events:
  - up-short
  - down-short
  - up-long
  - down-long and
  - release.
  The events are interpreted and actions are initiated accordingly by the target actuator unit. The double button sensor and the observer have no notion of the underlying function.

## Housing (FMC:Actor)
- dcterms:description: Diagramm:
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
## Press and hold Down-button (FMC:Actor)
- dcterms:description: Press down-button >x ms.

## Press and hold Up-button (FMC:Actor)
- dcterms:description: Press up-button >x ms.

## Release button (FMC:Actor)

## Shading (FMC:Actor)
- dcterms:description: Window-shade with 2 degrees of freedom: It can be moved up/down and the elements can be set straight/tilted. Both movements can be made proportionally with an electric drive.

## SmartHome Controller (FMC:Actor)
- dcterms:description: The controller
  - interconnects locally distributed sensors and actuators,
  - coordinates different actuators where appropriate and
  - performes automatic functions, such as switching external lamps dependend on ambient light.

## Start-decreasing (FMC:Actor)

## Start-increasing (FMC:Actor)

## Stop-decreasing (FMC:Actor)

## Stop-increasing (FMC:Actor)

## Switch-off (FMC:Actor)
- dcterms:description: Switch to programmed min-value.

## Switch-on (FMC:Actor)
- dcterms:description: Switch to programmed max-value.

## User (FMC:Actor)

## Wait for Activation (FMC:Actor)
- dcterms:description: The kind of activation is determined:
  - Up- or Down-Button
  - Short or long activation: 'Short' is < 0,4 sec.
  - Do only wait until the distinction between 'short' or 'long' can be made!

## Wait for Deactivation (FMC:Actor)

## Wireless Module (FMC:Actor)
- dcterms:description: Receives control commands via radio signal or the mechanical position of a mounted sensor unit. Sends electrical control signals to the mounted actuator module.

## Type 'State' (SpecIF:Heading)
- dcterms:description: A 'State' is a fundamental model element type representing a passive entity, be it a value, a condition, an information storage or even a physical shape.

## Actuator Rods (FMC:State)
- dcterms:description: Up to four actuator rods connecting the buttons to electrical contacts.

## Control Signals (FMC:State)

## down (FMC:State)
- dcterms:description: The button to drive down the dimmer, shading or similar devices.

## Electro-Magnetic Resistance (FMC:State)
- dcterms:description: Electromagnetic characteristics, especially EM-shielding.

## Flush-mounted Dimmer (FMC:State)
- dcterms:description: A dimmer for electric loads in an industry-standard mounting frame which is flush with the wall surface. In other words, the dimmer is sitting in the wall and just the buttons are visible.

## Flush-mounted Shading Control (FMC:State)

## Ground Cable (FMC:State)
- dcterms:description:
  - Cable-diameter
  - Wire-diameter
  - Max-current

## I/O Pins (FMC:State)
- dcterms:description: per input and output signal:
  - hardware-address
  - number of significant bits

## Intelligent Shading Drive (FMC:State)
- dcterms:description: An intelligent shading actuator with 2 drives for up/down straight/tilt motion. The unit comprises the control unit and the motors.

## Load Cable (FMC:State)
- dcterms:description:
  - Cable-diameter
  - Wire-diameter
  - Max-current

## M (FMC:State)
- dcterms:description: Actuator Motor 230V.

## Neutral Cable (FMC:State)
- dcterms:description:
  - Cable-diameter
  - Wire-diameter
  - Max-current

## Physical Space (FMC:State)
- dcterms:description: Effective 3D interior space and mounting for electronics.

## Processor RAM ROM (FMC:State)
- dcterms:description: EPROM-Size
  RAM-Size
  Processor type with instruction set and speed (MIPS)

## Remote Control (FMC:State)

## SmartHome System (FMC:State)
- dcterms:description: The new system for controlling all major functions of the private home:
  - light/illumination
  - window shades
  - heating
  - consumption meters for electricity, heat, gas and water.

## Spring Clips (FMC:State)
- dcterms:description: Spring clips for mechanical connection.

## straighten (FMC:State)
- dcterms:description: The button to straighten the shading elements.

## Supply Cable (FMC:State)
- dcterms:description:
  - Cable-diameter
  - Wire-diameter
  - Max-current

## Thermal Resistance (FMC:State)
- dcterms:description: Thermal resistance and thermal capacity of the [[housing]].

## tilt (FMC:State)
- dcterms:description: The button to tilt the shading elements.

## up (FMC:State)
- dcterms:description: The button to drive up the dimmer, shading or similar devices.

## Wireless Network (FMC:State)

## Type 'Event' (SpecIF:Heading)
- dcterms:description: An 'Event' is a fundamental model element type representing a time reference, a change in condition/value or more generally a synchronisation primitive.

## Decreasing (FMC:Event)

## Dim-down! (FMC:Event)

## Dim-up! (FMC:Event)

## Done! (FMC:Event)

## down-long! (FMC:Event)

## down-short! (FMC:Event)

## Increasing (FMC:Event)

## Intermediate (FMC:Event)

## max-reached! (FMC:Event)

## Maximum (FMC:Event)

## min-reached! (FMC:Event)

## Minimum (FMC:Event)

## released! (FMC:Event)

## Stop dimming! (FMC:Event)

## Switch-off! (FMC:Event)

## Switch-on! (FMC:Event)

## up-long! (FMC:Event)

## up-short! (FMC:Event)

## Parts List (SpecIF:Heading)
- dcterms:description: This Parts List has been automatically generated from the model.

## Open Issues (SpecIF:Heading)

## Mechanical (SpecIF:Heading)

## An open issue with respect to mechanics (SpecIF:Issue)
- dcterms:identifier: OPM_001
- dcterms:description: This is the description of the issue and potential solution.
- SpecIF:Status: in progress
- SpecIF:Priority: 3_low
- SpecIF:DueDate: 2012-09-30T12:00:00+02:00

## Software (SpecIF:Heading)

## An open issue concerning software (SpecIF:Issue)
- dcterms:identifier: OPS_001
- dcterms:description: A description.
- SpecIF:Status: rejected
- SpecIF:Priority: 2_medium
- SpecIF:Responsible: Vorname Nachname
- SpecIF:DueDate: 2012-09-30T12:00:00+02:00

## Statements
- SmartHome System SpecIF:shows Bulb
- SmartHome System SpecIF:shows down
- SmartHome System SpecIF:shows Flush-mounted Dimmer
- SmartHome System SpecIF:shows Flush-mounted Shading Control
- SmartHome System SpecIF:shows M
- SmartHome System SpecIF:shows Intelligent Shading Drive
- SmartHome System SpecIF:shows Remote Control
- SmartHome System SpecIF:shows SmartHome Controller
- SmartHome System SpecIF:shows Shading
- SmartHome System SpecIF:shows SmartHome System
- SmartHome System SpecIF:shows straighten
- SmartHome System SpecIF:shows tilt
- SmartHome System SpecIF:shows up
- SmartHome System SpecIF:shows User
- Flush-mounted Dimmer SpecIF:shows Actuator Rods
- Flush-mounted Dimmer SpecIF:shows Assembly Frame
- Flush-mounted Dimmer SpecIF:shows Control Signals
- Flush-mounted Dimmer SpecIF:shows Dimmer Module
- Flush-mounted Dimmer SpecIF:shows Double Button
- Flush-mounted Dimmer SpecIF:shows down
- Flush-mounted Dimmer SpecIF:shows Flush-mounted Dimmer
- Flush-mounted Dimmer SpecIF:shows Ground Cable
- Flush-mounted Dimmer SpecIF:shows Load Cable
- Flush-mounted Dimmer SpecIF:shows Neutral Cable
- Flush-mounted Dimmer SpecIF:shows Spring Clips
- Flush-mounted Dimmer SpecIF:shows Supply Cable
- Flush-mounted Dimmer SpecIF:shows up
- Flush-mounted Dimmer SpecIF:shows Wireless Module
- Flush-mounted Dimmer SpecIF:shows Wireless Network
- Dimmer Module SpecIF:shows Control Signals
- Dimmer Module SpecIF:shows Dimmer Controller Software
- Dimmer Module SpecIF:shows Dimmer Electronics
- Dimmer Module SpecIF:shows Dimmer Module
- Dimmer Module SpecIF:shows Electro-Magnetic Resistance
- Dimmer Module SpecIF:shows Ground Cable
- Dimmer Module SpecIF:shows Housing
- Dimmer Module SpecIF:shows I/O Pins
- Dimmer Module SpecIF:shows Load Cable
- Dimmer Module SpecIF:shows Neutral Cable
- Dimmer Module SpecIF:shows Physical Space
- Dimmer Module SpecIF:shows Processor RAM ROM
- Dimmer Module SpecIF:shows Spring Clips
- Dimmer Module SpecIF:shows Supply Cable
- Dimmer Module SpecIF:shows Thermal Resistance
- User Activity SpecIF:shows Briefly press Down-button
- User Activity SpecIF:shows Briefly press Up-button
- User Activity SpecIF:shows Dim-down!
- User Activity SpecIF:shows Dim-up!
- User Activity SpecIF:shows Done!
- User Activity SpecIF:shows Press and hold Down-button
- User Activity SpecIF:shows Press and hold Up-button
- User Activity SpecIF:shows Release button
- User Activity SpecIF:shows Stop dimming!
- User Activity SpecIF:shows Switch-off!
- User Activity SpecIF:shows Switch-on!
- User Activity SpecIF:shows User
- Double-Button Observer Software SpecIF:shows Double-Button Observer Software
- Double-Button Observer Software SpecIF:shows down-long!
- Double-Button Observer Software SpecIF:shows down-short!
- Double-Button Observer Software SpecIF:shows released!
- Double-Button Observer Software SpecIF:shows up-long!
- Double-Button Observer Software SpecIF:shows up-short!
- Double-Button Observer Software SpecIF:shows Wait for Activation
- Double-Button Observer Software SpecIF:shows Wait for Deactivation
- Dimmer Controller Software SpecIF:shows Decreasing
- Dimmer Controller Software SpecIF:shows Dimmer Controller Software
- Dimmer Controller Software SpecIF:shows down-long!
- Dimmer Controller Software SpecIF:shows down-short!
- Dimmer Controller Software SpecIF:shows Increasing
- Dimmer Controller Software SpecIF:shows Intermediate
- Dimmer Controller Software SpecIF:shows max-reached!
- Dimmer Controller Software SpecIF:shows Maximum
- Dimmer Controller Software SpecIF:shows min-reached!
- Dimmer Controller Software SpecIF:shows Minimum
- Dimmer Controller Software SpecIF:shows released!
- Dimmer Controller Software SpecIF:shows Start-decreasing
- Dimmer Controller Software SpecIF:shows Start-increasing
- Dimmer Controller Software SpecIF:shows Stop-decreasing
- Dimmer Controller Software SpecIF:shows Stop-increasing
- Dimmer Controller Software SpecIF:shows Switch-off
- Dimmer Controller Software SpecIF:shows Switch-on
- Dimmer Controller Software SpecIF:shows up-long!
- Dimmer Controller Software SpecIF:shows up-short!
- Dimmer Controller Software oslc_rm:satisfies Dim an electric load
- Dim an electric load SpecIF:dependsOn Set dimming parameters
- Dimmer Module oslc_rm:satisfies Dim an electric load
- Dimmer Electronics oslc_rm:satisfies Dim an electric load
- Dimmer Controller Software oslc_rm:satisfies Switch an electric load
- An open issue with respect to mechanics SpecIF:refersTo Switch an electric load
- Dimmer Controller Software oslc_rm:satisfies Set dimming parameters
- Double Button oslc_rm:satisfies Minimum button size
- Dimmer Electronics oslc_rm:satisfies Electric load is 120 W
- User oslc_rm:satisfies Instant use
- An open issue with respect to mechanics SpecIF:refersTo Instant use
- Dimmer Module oslc_rm:satisfies Instantaneous reaction
- Wireless Module oslc_rm:satisfies Instantaneous reaction
- SmartHome System oslc_rm:satisfies Consistent system behavior
- Dimmer Module oslc_rm:satisfies Consistent system behavior
- Flush-mounted Dimmer oslc_rm:satisfies No dead-locks
- Flush-mounted Shading Control oslc_rm:satisfies No dead-locks
- Intelligent Shading Drive oslc_rm:satisfies No dead-locks
- SmartHome Controller oslc_rm:satisfies No dead-locks
- No dead-locks SpecIF:dependsOn Complete state-machine
- Dimmer Electronics oslc_rm:satisfies Overload protection
- Intelligent Shading Drive oslc_rm:satisfies Overload protection
- Dimmer Electronics oslc_rm:satisfies Auto shut-off
- Intelligent Shading Drive oslc_rm:satisfies Auto shut-off
- SmartHome System oslc_rm:satisfies Compliance with industry standards
- Dimmer Module oslc_rm:satisfies Compliance with industry standards
- Flush-mounted Dimmer oslc_rm:satisfies Industry-standard mounting
- Flush-mounted Shading Control oslc_rm:satisfies Industry-standard mounting
- Flush-mounted Dimmer oslc_rm:satisfies Fire protection
- Intelligent Shading Drive oslc_rm:satisfies Fire protection
- Dimmer Module oslc_rm:satisfies Fire protection
- Dimmer Electronics oslc_rm:satisfies Galvanic Isolation
- Dimmer Controller Software oslc_rm:satisfies Complete state-machine
- Assembly Frame SpecIF:writes Spring Clips
- Assembly Frame SpecIF:reads Spring Clips
- Flush-mounted Dimmer SpecIF:contains Assembly Frame
- User SpecIF:contains Briefly press Down-button
- User SpecIF:contains Briefly press Up-button
- Bulb SpecIF:reads Flush-mounted Dimmer
- Dimmer Controller Software SpecIF:contains down-long!
- Dimmer Controller Software SpecIF:contains down-short!
- Dimmer Controller Software SpecIF:contains Intermediate
- Dimmer Controller Software SpecIF:contains max-reached!
- Dimmer Controller Software SpecIF:contains Maximum
- Dimmer Controller Software SpecIF:contains min-reached!
- Dimmer Controller Software SpecIF:contains Minimum
- Dimmer Controller Software SpecIF:contains released!
- Dimmer Controller Software SpecIF:contains Switch-off
- Dimmer Controller Software SpecIF:contains Switch-on
- Dimmer Controller Software SpecIF:contains up-long!
- Dimmer Controller Software SpecIF:contains up-short!
- Dimmer Controller Software SpecIF:reads I/O Pins
- Dimmer Controller Software SpecIF:reads Processor RAM ROM
- Dimmer Module SpecIF:contains Dimmer Controller Software
- Dimmer Electronics SpecIF:writes Ground Cable
- Dimmer Electronics SpecIF:reads Ground Cable
- Dimmer Electronics SpecIF:writes Load Cable
- Dimmer Electronics SpecIF:reads Load Cable
- Dimmer Electronics SpecIF:writes Neutral Cable
- Dimmer Electronics SpecIF:reads Neutral Cable
- Dimmer Electronics SpecIF:writes Supply Cable
- Dimmer Electronics SpecIF:reads Supply Cable
- Dimmer Electronics SpecIF:writes Processor RAM ROM
- Dimmer Electronics SpecIF:writes I/O Pins
- Dimmer Electronics SpecIF:reads Control Signals
- Dimmer Electronics SpecIF:reads Thermal Resistance
- Dimmer Electronics SpecIF:reads Electro-Magnetic Resistance
- Dimmer Electronics SpecIF:reads Physical Space
- Dimmer Module SpecIF:contains Dimmer Electronics
- Dimmer Module SpecIF:contains Housing
- Dimmer Module SpecIF:contains Electro-Magnetic Resistance
- Dimmer Module SpecIF:contains Processor RAM ROM
- Dimmer Module SpecIF:contains I/O Pins
- Dimmer Module SpecIF:contains Physical Space
- Dimmer Module SpecIF:contains Thermal Resistance
- Dimmer Module SpecIF:reads Control Signals
- Flush-mounted Dimmer SpecIF:contains Dimmer Module
- Double Button SpecIF:writes Spring Clips
- Double Button SpecIF:reads Spring Clips
- Double Button SpecIF:writes Actuator Rods
- Double Button SpecIF:reads down
- Double Button SpecIF:reads up
- Flush-mounted Dimmer SpecIF:contains Double Button
- Double-Button Observer Software SpecIF:contains down-long!
- Double-Button Observer Software SpecIF:contains down-short!
- Double-Button Observer Software SpecIF:contains released!
- Double-Button Observer Software SpecIF:contains up-long!
- Double-Button Observer Software SpecIF:contains up-short!
- Double-Button Observer Software SpecIF:contains Wait for Activation
- Double-Button Observer Software SpecIF:contains Wait for Deactivation
- An open issue with respect to mechanics SpecIF:refersTo Housing
- Housing SpecIF:writes Spring Clips
- Housing SpecIF:reads Spring Clips
- Housing SpecIF:writes Electro-Magnetic Resistance
- Housing SpecIF:writes Physical Space
- Housing SpecIF:writes Thermal Resistance
- User SpecIF:contains Press and hold Down-button
- User SpecIF:contains Press and hold Up-button
- User SpecIF:contains Release button
- Shading SpecIF:reads Intelligent Shading Drive
- SmartHome Controller SpecIF:writes Flush-mounted Dimmer
- SmartHome Controller SpecIF:reads Flush-mounted Dimmer
- SmartHome Controller SpecIF:writes Intelligent Shading Drive
- SmartHome Controller SpecIF:reads Flush-mounted Shading Control
- SmartHome Controller SpecIF:reads Remote Control
- SmartHome System SpecIF:contains SmartHome Controller
- User SpecIF:contains Dim-down!
- User SpecIF:contains Dim-up!
- User SpecIF:contains Done!
- User SpecIF:contains Stop dimming!
- User SpecIF:contains Switch-on!
- User SpecIF:contains Switch-off!
- User SpecIF:writes Remote Control
- User SpecIF:writes Flush-mounted Shading Control
- User SpecIF:writes Flush-mounted Dimmer
- Flush-mounted Dimmer SpecIF:contains Wireless Module
- Wireless Module SpecIF:writes Spring Clips
- Wireless Module SpecIF:reads Spring Clips
- Wireless Module SpecIF:writes Wireless Network
- Wireless Module SpecIF:reads Wireless Network
- Wireless Module SpecIF:writes Control Signals
- Wireless Module SpecIF:reads Actuator Rods
- Flush-mounted Dimmer SpecIF:contains Actuator Rods
- Flush-mounted Dimmer SpecIF:contains Control Signals
- Flush-mounted Dimmer SpecIF:contains down
- Flush-mounted Shading Control SpecIF:contains down
- Remote Control SpecIF:contains down
- Flush-mounted Dimmer SpecIF:contains up
- Flush-mounted Dimmer SpecIF:contains Spring Clips
- SmartHome System SpecIF:contains Flush-mounted Dimmer
- Flush-mounted Shading Control SpecIF:contains up
- Flush-mounted Shading Control SpecIF:contains straighten
- Flush-mounted Shading Control SpecIF:contains tilt
- SmartHome System SpecIF:contains Flush-mounted Shading Control
- Intelligent Shading Drive SpecIF:contains M
- SmartHome System SpecIF:contains Intelligent Shading Drive
- An open issue concerning software SpecIF:refersTo Remote Control
- Remote Control SpecIF:contains up
- SmartHome System SpecIF:contains Remote Control
